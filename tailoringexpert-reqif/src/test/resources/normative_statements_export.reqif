# Normative Statements
Exported normative statements

# Specification: Normative Statements

## Requirement: ECSS-Q-ST-80D Software product assurance
The supplier shall ensure that an organizational structure is defined for software development, and that individuals have defined tasks and responsibilities.
- Document code: Q-80
- Parent PUID: ECSS-Q-ST-80_0720001
- Discipline: Software product assurance programme implementation / Organization and responsibility / Organization
- Active: true
